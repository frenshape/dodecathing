import FreeCAD as App
from FreeCAD import Vector, Units, Console, Rotation, Matrix, Sketcher
from dodecathing.dodecathing import DodecaThing, ViewThing

if App.ActiveDocument:
    doc = FreeCAD.ActiveDocument
    a = App.ActiveDocument.addObject("Part::FeaturePython","DoDecaThing")
    b = DodecaThing(a)
    ViewThing(a.ViewObject)
    doc.recompute()
else:
    Console.PrintMessage("No active document")
